# ***************************************************************************
# *                                                                         *
# *   Copyright (c) 2024 - Harry van Langen <hvlanalysis@gmail.com>        *
# *                                                                         *
# *   This program is free software; you can redistribute it and/or modify  *
# *   it under the terms of the GNU Lesser General Public License (LGPL)    *
# *   as published by the Free Software Foundation; either version 2 of     *
# *   the License, or (at your option) any later version.                   *
# *   for detail see the LICENCE text file.                                 *
# *                                                                         *
# *   This program is distributed in the hope that it will be useful,       *
# *   but WITHOUT ANY WARRANTY; without even the implied warranty of        *
# *   MERCHANTABILITY or FITNESS FOR A PARTICULAR PURPOSE.  See the         *
# *   GNU Library General Public License for more details.                  *
# *                                                                         *
# *   You should have received a copy of the GNU Library General Public     *
# *   License along with this program; if not, write to the Free Software   *
# *   Foundation, Inc., 59 Temple Place, Suite 330, Boston, MA  02111-1307  *
# *   USA                                                                   *
# *                                                                         *
# ***************************************************************************

import os
import sys
import dummyES
import numpy as np
import FreeCAD as App
import FreeCADGui as Gui
from PySide2 import QtWidgets, QtGui, QtCore

mdir = os.path.dirname(dummyES.file_path())
name = App.ActiveDocument.Label
file_path = os.path.join(mdir, "control files", name + '.inp')
macro_path = os.path.join(mdir, 'source code')

if 'fcES' in sys.modules.keys():
    del (sys.modules['fcES'])
else:
    sys.path.append(macro_path)

import fcES as ft

rv = FCmw.findChild(QtWidgets.QTextEdit, "Report view")
rv.clear()

FCmw = Gui.getMainWindow()
doc = App.ActiveDocument


def main(ft, mesh, s, mdir, name):

    file_path = os.path.join(mdir, "output files", name + '.es')

    with open(file_path, "w") as f:
        f.write("model name:{0: >30}\n\n".format(name))
        f.write("average values")
        print("average values")
        f.write(
            "\n=========================================================================================================================\n\n")

        f.write(
            "{0: >10}{1: >10}{2: >10}{3: >10}    {4}\n".format("Length", "peeq", "CSR", "svmises", "edge"))
        if len(Edge_Names)>0:
            print(
                "{0: >10}{1: >10}{2: >10}{3: >10}    {4}".format("Length", "peeq", "CSR", "svmises", "edge"))

        for index, edge in enumerate(Edge_Names):
            f.write(
                '{0: >10.2e}{1: >10.2e}{2: >10.2e}{3: >10.2e}    {4}\n'.format(
                    edge_length[index], edge_peeq[index], edge_CSR[index], edge_svm[index], edge))
            print(
                '{0: >10.2e}{1: >10.2e}{2: >10.2e}{3: >10.2e}    {4}'.format(
                    edge_length[index], edge_peeq[index], edge_CSR[index], edge_svm[index], edge))

            # print("{} average values".format(edge))
            # print(
            #     "{0: >10}{1: >10}{2: >10}{3: >10}".format("Length", "peeq", "CSR", "svmises"))
            # print(
            #     '{0: >10.2e}{1: >10.2e}{2: >10.2e}{3: >10.2e}'.format(
            #         edge_length[index], edge_peeq[index], edge_CSR[index], edge_svm[index]))

        f.write(
            "\n=========================================================================================================================\n\n")

        f.write(
            "{0: >10}{1: >10}{2: >10}{3: >10}    {4}\n".format("Area", "peeq", "CSR", "svmises", "face"))
        if len(Face_Names)>0:
            print(
                "{0: >10}{1: >10}{2: >10}{3: >10}    {4}".format("Area", "peeq", "CSR", "svmises", "face"))

        for index, face in enumerate(Face_Names):
            f.write(
                '{0: >10.2e}{1: >10.2e}{2: >10.2e}{3: >10.2e}    {4}\n'.format(
                    face_area[index], face_peeq[index], face_CSR[index], face_svm[index], face))
            print(
                '{0: >10.2e}{1: >10.2e}{2: >10.2e}{3: >10.2e}    {4}'.format(
                    face_area[index], face_peeq[index], face_CSR[index], face_svm[index], face))

        f.write(
            "\n=========================================================================================================================\n\n")

    f.close()


main(ft, mesh, s, mdir, name)
