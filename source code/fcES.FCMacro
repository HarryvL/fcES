# ***************************************************************************
# *                                                                         *
# *   Copyright (c) 2024 - Harry van Langen <hvlanalysis@gmail.com>        *
# *                                                                         *
# *   This program is free software; you can redistribute it and/or modify  *
# *   it under the terms of the GNU Lesser General Public License (LGPL)    *
# *   as published by the Free Software Foundation; either version 2 of     *
# *   the License, or (at your option) any later version.                   *
# *   for detail see the LICENCE text file.                                 *
# *                                                                         *
# *   This program is distributed in the hope that it will be useful,       *
# *   but WITHOUT ANY WARRANTY; without even the implied warranty of        *
# *   MERCHANTABILITY or FITNESS FOR A PARTICULAR PURPOSE.  See the         *
# *   GNU Library General Public License for more details.                  *
# *                                                                         *
# *   You should have received a copy of the GNU Library General Public     *
# *   License along with this program; if not, write to the Free Software   *
# *   Foundation, Inc., 59 Temple Place, Suite 330, Boston, MA  02111-1307  *
# *   USA                                                                   *
# *                                                                         *
# ***************************************************************************

import os
import sys
import dummyES
import numpy as np
import FreeCAD as App
import matplotlib.pyplot as plt
from scipy.optimize import nnls

global np
global plt
global mdir
global nnls
global name
global plots
global results
global macro_path
global inp_file_path

print("fcES.FCMacro")

mdir = os.path.dirname(dummyES.file_path())
name = App.ActiveDocument.Label
inp_file_path = os.path.join(mdir, "control files", name + '.inp')
macro_path = os.path.join(mdir, 'source code')

global calc_S


def calc_S(L, k, EI, q1, q2):
    lam = (k / (4 * EI)) ** 0.25
    s = np.sin(lam * L)
    c = np.cos(lam * L)
    Sh = np.sinh(lam * L)
    Ch = np.cosh(lam * L)

    d = k * (Sh ** 2 - s ** 2)

    # Compliance matrix
    C = np.zeros((4, 4))
    C[0, 0] = 2 * lam * (Sh * Ch - s * c)
    C[1, 0] = -2 * lam ** 2 * (Sh ** 2 + s ** 2)
    C[2, 0] = 2 * lam * (Sh * c - s * Ch)
    C[3, 0] = -4 * lam ** 2 * Sh * s
    C[1, 1] = 4 * lam ** 3 * (Sh * Ch + s * c)
    C[2, 1] = -C[3, 0]
    C[3, 1] = 4 * lam ** 3 * (Sh * c + s * Ch)
    C[2, 2] = C[0, 0]
    C[3, 2] = -C[1, 0]
    C[3, 3] = C[1, 1]
    C[0, 1] = C[1, 0]
    C[0, 2] = C[2, 0]
    C[0, 3] = C[3, 0]
    C[1, 2] = C[2, 1]
    C[1, 3] = C[3, 1]
    C[2, 3] = C[3, 2]

    C /= d

    S = np.linalg.inv(C)

    A11 = (Sh * s) / (2 * L * lam ** 2)
    A12 = (s * Ch - c * Sh) / (4 * L * lam ** 2)
    A13 = (1 - c * Ch) / (4 * L * lam ** 2)
    A14 = (2 * L * lam - Ch * s - c * Sh) / (8 * L * lam ** 2)
    A21 = (L * lam * Ch * s + (L * lam * c - s) * Sh) / (2 * L * lam ** 2)
    A22 = (-Ch * s + (c + 2 * L * lam * s) * Sh) / (4 * L * lam ** 2)
    A23 = (-1 + Ch * (c + L * lam * s) - L * lam * c * Sh) / (4 * L * lam ** 2)
    A24 = (Ch * (-2 * L * lam * c + s) + c * Sh) / (8 * L * lam ** 2)

    F1 = np.zeros(4)
    F1[0] = A11 - (S[0, 1] / (lam ** 2 * EI)) * A13 + (
            S[0, 0] / (lam ** 3 * EI)) * A14
    F1[1] = A12 / lam - (S[1, 1] / (lam ** 2 * EI)) * A13 + (
            S[0, 1] / (lam ** 3 * EI)) * A14
    F1[2] = -(S[1, 2] / (lam ** 2 * EI)) * A13 + (
            S[0, 2] / (lam ** 3 * EI)) * A14
    F1[3] = -(S[1, 3] / (lam ** 2 * EI)) * A13 + (
            S[0, 3] / (lam ** 3 * EI)) * A14

    F2 = np.zeros(4)
    F2[0] = A21 - (S[0, 1] / (lam ** 2 * EI)) * A23 + (
            S[0, 0] / (lam ** 3 * EI)) * A24
    F2[1] = A22 / lam - (S[1, 1] / (lam ** 2 * EI)) * A23 + (
            S[0, 1] / (lam ** 3 * EI)) * A24
    F2[2] = -(S[1, 2] / (lam ** 2 * EI)) * A23 + (
            S[0, 2] / (lam ** 3 * EI)) * A24
    F2[3] = -(S[1, 3] / (lam ** 2 * EI)) * A23 + (
            S[0, 3] / (lam ** 3 * EI)) * A24

    F = q1 * F1 + q2 * F2

    return C, S, F


def results(npoint, num_el, analysis_type, node_obj, beam_obj, tank_obj, a):
    z = []
    M_z = []
    Q_z = []
    w_z = []
    sig_z = []
    sig_m = 0
    sig_a = 0

    for i in range(num_el):
        el = i + 1
        z0 = float(node_obj[el][0])
        z1 = float(node_obj[el + 1][0])
        L = z1 - z0
        if analysis_type == "beam":
            k = float(beam_obj[el][0])
            EI = float(beam_obj[el][1])
            q1 = float(beam_obj[el][2])
            q2 = float(beam_obj[el][3])
        else:
            R = float(tank_obj[el][0])
            E = float(tank_obj[el][1])
            t = float(tank_obj[el][2])
            nu = float(tank_obj[el][3])
            q1 = float(tank_obj[el][4])
            q2 = float(tank_obj[el][5])
            k = E * t / R ** 2
            EI = E * t ** 3 / 12.0 / (1.0 - nu ** 2)
        C, S, F = calc_S(L, k, EI, q1, q2)
        dof1 = 2 * i
        a_el = a[dof1:dof1 + 4]
        Q0 = -np.dot(S[0], a_el) + F[0]
        M0 = np.dot(S[1], a_el) - F[1]

        w0 = a_el[0]
        phi0 = a_el[1]
        lam = (k / (4 * EI)) ** 0.25

        for i in range(npoint + 1):
            zz = i * (z1 - z0) / npoint
            z.append(z0 + zz)
            Shz = np.sinh(lam * zz)
            Chz = np.cosh(lam * zz)
            sz = np.sin(lam * zz)
            cz = np.cos(lam * zz)
            F1 = Chz * cz
            F2 = 0.5 * (Chz * sz + Shz * cz)
            F3 = 0.5 * Shz * sz
            F4 = 0.25 * (Chz * sz - Shz * cz)
            q_z = q1 * (1 - zz / L) + q2 * zz / L
            int1 = (L * q1 * lam * Chz * sz + (
                    L * q1 * lam * cz + (-q1 + q2) * sz) * Shz) / (
                           2 * L * lam ** 2)
            int2 = -((q1 - q2) * Chz * sz + (
                    (-q1 + q2) * cz - 2 * L * q1 * lam * sz) * Shz) / (
                           4 * L * lam ** 2)
            int4 = (2 * q_z * L * lam + Chz * (
                    -2 * L * q1 * lam * cz + (q1 - q2) * sz) + (
                            q1 - q2) * cz * Shz) / (
                           8 * L * lam ** 2)

            w_z.append(
                w0 * F1 + 1 / lam * phi0 * F2 - M0 / lam ** 2 / EI * F3 - Q0 / lam ** 3 / EI * F4 + int4 / (
                        lam ** 3 * EI))

            M_z.append(
                M0 * F1 + Q0 / lam * F2 + w0 * k / lam ** 2 * F3 + phi0 * k / lam ** 3 * F4 - int2 / lam)

            Q_z.append(
                Q0 * F1 + w0 * k / lam * F2 + phi0 * k / lam ** 2 * F3 - 4 * M0 * lam * F4 - int1)

            if analysis_type == "tank" or analysis_type == "tendon":
                sig_z.append(6 * M_z[-1] / t ** 2)

    Q_m = np.max(np.abs(Q_z))
    M_m = np.max(np.abs(M_z))
    w_m = np.max(np.abs(w_z))
    if analysis_type != "beam":
        sig_m = 6 * M_m / t ** 2

    Q_a = np.average(Q_z)
    M_a = np.average(M_z)
    w_a = np.average(w_z)
    if analysis_type != "beam":
        sig_a = np.average(sig_z)

    if Q_m - np.abs(Q_a) < 1.0e-3 * np.abs(Q_a):
        Q_z = Q_a * np.ones(len(Q_z))
    if M_m - np.abs(M_a) < 1.0e-3 * np.abs(M_a):
        M_z = M_a * np.ones(len(M_z))
    if analysis_type != "beam":
        if sig_m - np.abs(sig_a) < 1.0e-3 * np.abs(sig_a):
            sig_z = sig_a * np.ones(len(sig_z))
    if w_m - np.abs(w_a) < 1.0e-3 * np.abs(w_a):
        w_z = w_a * np.ones(len(w_z))

    return np.array(z), np.array(w_z), np.array(Q_z), np.array(M_z), np.array(
        sig_z), np.array(w_m), np.array(
        Q_m), np.array(M_m), np.array(sig_m)


def plots(title, analysis_type, z, w_z, Q_z, M_z, sig_z, w_m, Q_m, M_m, sig_m):
    if analysis_type == "beam":
        fig, axes = plt.subplots(3, 1, figsize=(10, 10),
                                 constrained_layout=True)
    else:
        fig, axes = plt.subplots(2, 2, figsize=(10, 10),
                                 constrained_layout=True)
        axes = axes.flatten()

    axes[0].plot(z, w_z / w_m, color='red', linewidth=2)
    axes[0].grid(True, linestyle='-', alpha=1.0)
    axes[0].set_xlabel('z', fontsize=14)
    axes[0].set_ylabel(r'w/|w|$_{{\text{{max}}}}$ {0:s}'.format(""),
                       fontsize=14)
    axes[0].set_title(
        r'displacement |w|$_{{\text{{max}}}}$ = {0:.4e}'.format(w_m),
        fontsize=14)
    axes[0].invert_yaxis()

    axes[1].plot(z, Q_z / Q_m, color='green', linewidth=2)
    axes[1].grid(True, linestyle='-', alpha=1.0)
    axes[1].set_xlabel('z', fontsize=14)
    axes[1].set_ylabel(r'Q/|Q|$_{{\text{{max}}}}$ {0:s}'.format(""),
                       fontsize=14)
    axes[1].set_title(
        r'shear force |Q|$_{{\text{{max}}}}$ = {0:.4e}'.format(Q_m),
        fontsize=14)
    axes[1].invert_yaxis()

    axes[2].plot(z, M_z / M_m, color='blue', linewidth=2)
    axes[2].grid(True, linestyle='-', alpha=1.0)
    axes[2].set_xlabel('z', fontsize=14)
    axes[2].set_ylabel(r'M/|M|$_{{\text{{max}}}}$ {0:s}'.format(""),
                       fontsize=14)
    axes[2].set_title(
        r'bending moment |M|$_{{\text{{max}}}}$ = {0:.4e}'.format(M_m),
        fontsize=14)
    axes[2].invert_yaxis()

    if analysis_type != "beam":
        axes[3].plot(z, sig_z / sig_m, color='purple',
                     linewidth=2)  # Replace with your data
        axes[3].grid(True, linestyle='-', alpha=1.0)
        axes[3].set_xlabel('z', fontsize=14)
        axes[2].set_ylabel(r'sig/|sig|$_{{\text{{max}}}}$ {0:s}'.format(""),
                           fontsize=14)
        axes[3].set_title(
            r'bending stress |sig|$_{{\text{{max}}}}$ = {0:.4e}'.format(sig_m),
            fontsize=14)
        axes[3].invert_yaxis()

    for ax in axes:
        ax.grid(which="major", linewidth=1.0)  # Configure major gridlines
        ax.grid(which="minor", linewidth=0.2)  # Configure minor gridlines
        ax.minorticks_on()  # Enable minor ticks

    mng = plt.get_current_fig_manager()

    try:
        # TkAgg Backend
        mng.window.attributes('-fullscreen', True)  # Temporarily fullscreen
        screen_width = mng.window.winfo_screenwidth()
        screen_height = mng.window.winfo_screenheight()
        mng.window.attributes('-fullscreen', False)  # Exit fullscreen
        mng.window.geometry(
            f"{screen_width / 2}x{screen_height}+0+0")  # Half-width, full height
    except AttributeError:
        try:
            # Qt Backend
            screen = mng.window.screen()
            geometry = screen.geometry()
            screen_width, screen_height = geometry.width(), geometry.height()
            mng.window.setGeometry(0, 0, screen_width // 2,
                                   screen_height)  # Half width, full height
        except AttributeError:
            pass  # Unsupported backend fallback

    fig.canvas.manager.set_window_title(title)
    plt.show()


def objective(x, M, c):
    return np.linalg.norm(M @ x - c) ** 2


def main():
    node_obj = {}
    beam_obj = {}
    tank_obj = {}

    if 'fcES' in sys.modules.keys():
        del (sys.modules['fcES'])
        print("fcES in sys.modules.keys")
    else:
        sys.path.append(macro_path)
        print("fcES path added")

    try:
        with open(inp_file_path, "r") as file:
            lines = file.readlines()
        if lines:
            analysis_type = lines[0].split("=")[1].strip()
            num_el = int(lines[1].split("=")[1].strip())

            # Parse remaining lines
            for line in lines[2:]:
                line = line.strip()
                if line.startswith("node"):
                    key, values = line.split(":")
                    key = int(key.split()[1])  # Extract the node number
                    node_obj[key] = values.strip().split()
                elif line.startswith("beam"):
                    key, values = line.split(":")
                    key = int(key.split()[1])  # Extract the beam number
                    beam_obj[key] = values.strip().split()
                elif line.startswith("tank"):
                    key, values = line.split(":")
                    key = int(key.split()[1])  # Extract the tank number
                    tank_obj[key] = values.strip().split()
                elif line.startswith("tendon_load"):
                    tendon_load = float(line.split("=")[1].strip())

    except FileNotFoundError:
        print("file not found")

    num_node = num_el + 1
    ndof = 2 * num_node
    GSM = np.zeros((ndof, ndof), dtype=np.float64)
    GF = np.zeros(ndof, dtype=np.float64)

    Q = []
    M = []
    fix1 = []
    fix2 = []
    npoint = 100

    for i in range(num_node):
        nd = i + 1
        Q.append(float(node_obj[nd][3]))
        M.append(float(node_obj[nd][4]))
        fix1.append(node_obj[nd][1])
        fix2.append(node_obj[nd][2])

    for i in range(num_el):
        nd = i + 1
        el = i + 1
        z1 = float(node_obj[nd][0])
        z2 = float(node_obj[nd + 1][0])
        L = z2 - z1

        if analysis_type == "beam":
            k = float(beam_obj[el][0])
            EI = float(beam_obj[el][1])
            q1 = float(beam_obj[el][2])
            q2 = float(beam_obj[el][3])
        else:
            R = float(tank_obj[el][0])
            E = float(tank_obj[el][1])
            t = float(tank_obj[el][2])
            nu = float(tank_obj[el][3])
            q1 = float(tank_obj[el][4])
            q2 = float(tank_obj[el][5])
            k = E * t / R ** 2
            EI = E * t ** 3 / 12.0 / (1.0 - nu ** 2)

        C, S, F = calc_S(L, k, EI, q1, q2)
        GSM[2 * i:2 * i + 4, 2 * i:2 * i + 4] += S
        GF[2 * i:2 * i + 4] += F

    for nd in range(num_node):
        GF[2 * nd] += Q[nd]
        GF[2 * nd + 1] += M[nd]

    ndof = 2 * num_el + 2
    zeros = np.zeros(ndof)
    active = np.ones(num_el + 1, dtype=np.int32)
    for nd in range(num_node):
        if fix1[nd] == "y" or fix1[nd] == "Y":
            dof = 2 * nd
            GSM[dof] = zeros
            GSM[:, dof] = zeros
            GSM[dof, dof] = 1.0
            GF[dof] = 0.0
            active[nd] = 0
        if fix2[nd] == "y" or fix1[nd] == "Y":
            dof = 2 * nd + 1
            GSM[dof] = zeros
            GSM[:, dof] = zeros
            GSM[dof, dof] = 1.0
            GF[dof] = 0.0

    GSM_inv = np.linalg.inv(GSM)

    a = np.dot(GSM_inv, GF)
    z, w_z, Q_z, M_z, sig_z, w_m, Q_m, M_m, sig_m = results(npoint, num_el,
                                                            analysis_type,
                                                            node_obj, beam_obj,
                                                            tank_obj,
                                                            a)

    plots("no pre-stress", analysis_type, z, w_z, Q_z, M_z, sig_z, w_m, Q_m,
          M_m, sig_m)

    if analysis_type == "tendon":
        x_tot = np.zeros(num_node, dtype=np.float64)
        x_tot_old = np.ones(num_node, dtype=np.float64)
        num_repeat = 0
        change = 1.0
        c = 6 * np.array(M_z.copy()) / t ** 2
        A = np.zeros((num_el * (npoint + 1), num_node), dtype=np.float64)
        for el in range(num_el):
            tank_obj[el + 1][4] = "0.0"
            tank_obj[el + 1][5] = "0.0"
        for nd in range(num_node):
            GF = np.zeros(ndof, dtype=np.float64)
            GF[2 * nd] = 1.0
            a = np.dot(GSM_inv, GF)
            _, _, _, A_c, _, _, _, _, _ = results(npoint, num_el,
                                                  analysis_type, node_obj,
                                                  beam_obj, tank_obj,
                                                  a)
            A[:, nd] = 6 * A_c / t ** 2

        while change > 1.0e-6 and num_repeat < 50:
            num_repeat += 1
            x_tot_old = x_tot.copy()

            A_red = np.delete(A, np.where(np.array(active) == 0)[0], axis=1)

            x, _ = nnls(A_red, c)

            count = 0
            for nd, act in enumerate(active):
                if act:
                    x_tot[nd] = x[count]
                    count += 1
                else:
                    x_tot[nd] = 0.0

            change = np.linalg.norm(x_tot - x_tot_old)

            for nn, xn in enumerate(x_tot):
                if xn < tendon_load / R:
                    active[nn] = 0
                    x_tot[nn] = 0.0

        for nn, act in enumerate(active):
            GF[2 * nn] = x_tot[nn]

        a = np.dot(GSM_inv, GF)

    if analysis_type == "tendon":
        z, wp_z, Qp_z, Mp_z, sigp_z, wp_m, Qp_m, Mp_m, sigp_m = results(npoint,
                                                                        num_el,
                                                                        analysis_type,
                                                                        node_obj,
                                                                        beam_obj,
                                                                        tank_obj,
                                                                        a)
        plots("pre-stress", analysis_type, z, wp_z, Qp_z, Mp_z, sigp_z, wp_m,
              Qp_m, Mp_m, sigp_m)

        plots("combined (no prestress - pre-stress / 2)", analysis_type, z,
              w_z - wp_z / 2, Q_z - Qp_z / 2, M_z - Mp_z / 2,
              sig_z - sigp_z / 2, np.max(w_z - wp_z / 2), np.max(Q_z - Qp_z / 2),
              np.max(M_z - Mp_z / 2), np.max(sig_z - sigp_z / 2))

    file_path = os.path.join(mdir, "output files", name + '.es')

    with open(file_path, "w") as f:
        f.write("model name:{0: >10}\n".format(name))
        f.write(
            "\n=========================================================================================================================\n\n")
        f.write(f"number of elements    : {num_el: >10d}\n")
        f.write(f"maximum displacement  : {w_m: >10.2e}\n")
        f.write(f"maximum shear force   : {Q_m: >10.2e}\n")
        f.write(f"maximum bending moment: {M_m: >10.2e}\n")
        if analysis_type == "tank" or analysis_type == "tendon":
            f.write(f"maximum longitudinal stress: {sig_m}")
        if analysis_type == "tendon":
            f.write(
                "\n=========================================================================================================================\n\n")
            f.write("{0: >7}{1: >10}\n".format("tendon", "load"))
            for i, ft in enumerate(x_tot):
                f.write("{0: >7d}{1: >10.2e}\n".format(i, ft * R / 2))

        f.write(
            "\n=========================================================================================================================\n\n")

        if analysis_type == "beam":
            f.write(
                "{0: >10}{1: >10}{2: >10}{3: >10}\n".format("z_coor.", "disp.",
                                                            "shear", "moment"))
        else:
            f.write(
                "{0: >10}{1: >10}{2: >10}{3: >10}{4: >10}\n".format("z_coor.",
                                                                    "disp.",
                                                                    "shear",
                                                                    "moment",
                                                                    "stress"))
        for i in range(len(z)):
            if analysis_type == "beam":
                f.write(
                    "{0: >10.2e}{1: >10.2e}{2: >10.2e}{3: >10.2e}\n".format(
                        z[i], w_z[i], Q_z[i], M_z[i]))
            else:
                f.write(
                    "{0: >10.2e}{1: >10.2e}{2: >10.2e}{3: >10.2e}{4: >10.2e}\n".format(
                        z[i], w_z[i], Q_z[i], M_z[i], M_z[i] / (t ** 2 / 6)))

        f.write(
            "\n=========================================================================================================================\n\n")

    f.close()

if __name__ == "__main__":
    main()
